' =====================================================================
'  DRAWING AUTOMATION — Main Assembly  (rule name: DwgAutomate)
'  Output: ONE multi-sheet drawing in the template's native format (.dwg)
'    Sheet 1     = MAIN ASSEMBLY iso view + Parts-Only parts list + balloons
'    Sheet 2..N  = one sheet per UNIQUE part:
'                  FRONT / TOP / RIGHT in THIRD-ANGLE arrangement + ISO,
'                  auto-scaled to fit the sheet (A3), border + title block
'                  copied from sheet 1
'
'  Run with the main .iam as the ACTIVE document.
'  Structured as External Rule (Sub Main + helpers) — required by the parser.
'
'  v2 — changes after the first successful baseline run:
'   * Views are no longer fixed 1:1: each view is created 1:1, measured via
'     .Width/.Height, rescaled to fit, snapped to a standard scale
'     (measure-then-rescale pattern lifted from working code: JRForman/createSheets)
'   * Part sheets get FRONT/TOP/RIGHT + ISO. They are independent base views
'     with explicit orientations (NOT AddProjectedView) so the third-angle
'     ARRANGEMENT is guaranteed even if the template's drafting standard is
'     first-angle (typical for DIN templates). Trade-off: views are not
'     alignment-linked if dragged manually later.
'   * New sheets get the border + title block from sheet 1 (baseline run
'     produced bare sheets).
'   * PartsLists.Add third arg is a PartsListLevelEnum passed as raw value:
'     46594 = kPartsOnly, 46593 = kStructured (numeric values confirmed in
'     createSheets, which calls Add(view, point, 46593) in production).
'     Replaces the Boolean-arg guess that failed in the baseline run.
'
'  v3 — folded in Inventor's own iLogic snippet browser for this exact build
'  (macro recording is unavailable here, so these shipped snippets are the
'  best available ground truth — equivalent to a recorded macro):
'   * AddViewSafe was silently missing the view-name argument added in v2's
'     rewrite (regression vs. the working baseline, which named "MAIN
'     ASSEMBLY" successfully — visible in the browser tree screenshot as
'     "ANSICHT1:MASTER FILE v1.iam"). Restored.
'   * ApplySheetFormat now assigns border/title block by NAME through the
'     ThisDrawing wrapper (Sheet.Border = "name" / .TitleBlock = "name"),
'     confirmed-real snippets ("Change Border" / "Change Title Block").
'     Falls back to AddDefaultBorder/AddTitleBlock(name) if the wrapper
'     doesn't resolve correctly (see CONFIRM note on AutoBalloonView).
'   * New sheets mirror sheet 1's paper Size (Sheets.Add() does not reliably
'     inherit it) — matters since the company template is A3.
'   * AutoBalloon rewritten again: the snippet browser confirms a real bulk
'     call, View.Balloons.AttachToComponent(occurrenceName) (from "Balloon
'     Include"/"Balloon Exclude"/"Reattach Balloons"), which is exactly
'     "auto-balloon this component" without needing to compute any geometry
'     ourselves. Replaces the v2 CreateGeometryIntent + ring-math version
'     built from API memory, which is no longer needed.
'   * Remaining open question: ThisDrawing/ActiveSheet in this wrapper API
'     normally refers to whatever Inventor considers the active drawing.
'     This rule is an External Rule launched with the ASSEMBLY as ThisDoc,
'     which then creates and activates a new DrawingDocument mid-run via
'     Documents.Add(..., True). Whether ThisDrawing tracks that switch within
'     the same rule execution is NOT yet confirmed — wrapped in Try/Catch
'     with a fallback, per the established pattern. Check Logger output.
'
'  v4 — sheet metal parts (e.g. the stair stringer, per the reference sheet
'  the user provided) get a different, industry-standard layout instead of
'  FRONT/TOP/RIGHT+ISO: FLAT PATTERN + BEND TABLE + a folded ISO for
'  reference. Detected via TypeOf ... Is SheetMetalComponentDefinition (same
'  defensive TypeOf pattern already used for the assembly-level Weldment
'  check, rather than an "IsSheetMetal" property that may not exist, or the
'  "Document SubType Name" iProperty string, which is UI-language-dependent —
'  this install appears to be German going by the part names).
'   * Flat pattern view: ViewInfo NameValueMap with "SheetMetalFoldedModel" =
'     False — confirmed-in-the-wild (createSheets-style production code, same
'     source repo already mined for the PartsLists.Add enum values), not a
'     fresh guess.
'   * Bend table: Sheet.BendTables.Add(flatView, point) — this one IS a fresh
'     guess, not present anywhere in the snippet dump or the linked repos.
'     Try/Catch-wrapped; if it throws, check "oSheet.BendTables.Add(" via
'     IntelliSense in the iLogic editor (same verification method that fixed
'     PartsLists.Add earlier) and update BuildSheetMetalViews().
'   * Folded ISO view reuses the existing AddViewSafe/kIsoTopRightViewOrientation
'     path with no special options — createSheets shows this is what makes it
'     default to the FOLDED shape rather than flat.
'   * Layout percentages are a rough match to the reference sheet, not an
'     exact one — same "functional, not beautiful, may need a manual nudge"
'     caveat already given for balloon placement.
'
'  v5 — a real runtime log from the user's Inventor build resolved several
'  open questions DEFINITIVELY (not just "still unverified"):
'   * ThisDrawing is confirmed architecturally unusable here, not just
'     unreliable: the runtime error is literally 'ThisDrawing: This
'     document "MASTER FILE v1.iam" is not a drawing.' every time. It can
'     only ever refer to whatever document HOSTS the running rule (the
'     assembly), never to a drawing created programmatically mid-run.
'     Removed entirely — border/title block and balloons are back to pure
'     classic-COM calls.
'   * AutoBalloonView reverted to the CreateGeometryIntent + Balloons.Add
'     approach from v2, which the same log actually confirmed working
'     ("5 balloon(s) placed on sheet 'MAIN ASSEMBLY:1'." with zero
'     warnings) before v3 replaced it with the now-dead ThisDrawing route.
'   * ApplySheetFormat: title block has now failed the SAME E_INVALIDARG
'     three different ways (definition object, name string, name string
'     via wrapper) — never "member not found", so the call exists but
'     doesn't like what's been passed so far. Two new attempts added
'     (document-default parameterless call; a FRESH TitleBlockDefinition
'     looked up from the document's own collection rather than reusing
'     sheet 1's applied-instance object/name). If both fail too, the
'     logged message asks for an IntelliSense check instead of a fourth
'     blind guess.
'   * Sheet.BendTables confirmed WRONG — not a parameter issue like the
'     others, a clean "Public member 'BendTables' on type 'Sheet' not
'     found." Left Try/Catch-wrapped (still degrades gracefully) but the
'     log message now asks for an IntelliSense/autocomplete check rather
'     than implying another guess is coming — no confident second name to try.
'   * Added a best-effort attempt at "retrieve all model dimensions" on
'     every view (main assembly, FRONT/TOP/RIGHT/ISO, flat pattern):
'     NameValueMap key "RetrieveDimensions" = True, mirroring the Base
'     View dialog's "Retrieve Dimensions" checkbox and the same key/value
'     pattern as the already-confirmed "SheetMetalFoldedModel". This is a
'     FRESH, UNCONFIRMED guess — but unlike a wrong enum or member name, an
'     unrecognized NameValueMap key is typically ignored rather than
'     erroring, so the downside if the key name is wrong is just "no
'     dimensions appear", not a broken view. Falls back to the confirmed-
'     working plain AddBaseView call if this form throws at all.
'     IMPORTANT even if the key name is exactly right: this can only pull
'     in dimensions the PART's own author already marked "Include in
'     Drawing Views" in that part's modeling environment. If the parts
'     don't have any dimensions flagged for export, nothing will appear
'     here no matter what this rule does — that's a modeling-side setting,
'     not something drawing automation can create from scratch.
'
'  v6 — a COMPILE error (not a runtime exception) surfaced a new, more
'  serious risk class. v5's "oSheet.AddTitleBlock()" with zero arguments
'  didn't just fail — it triggered a hard compile error ("Argument not
'  specified for parameter 'TitleBlockDefinition'"), which blocks the
'  ENTIRE rule from running at all. Try/Catch cannot protect against
'  this: the rule never starts executing, so there's no partial progress,
'  no sheets, not even the first BOM-count log line — strictly worse than
'  any runtime E_INVALIDARG or "member not found" seen so far, both of
'  which at least let the rest of the rule keep going.
'   * Distinction to keep in mind for anything added later: wrong
'     enum/identifier names AND wrong argument COUNTS against a method
'     with a known strongly-typed signature are COMPILE-time failures
'     (unrescuable by Try/Catch — the whole rule aborts silently from the
'     user's point of view, before Logger ever runs). Wrong argument
'     VALUES and unknown MEMBER names on an otherwise-valid object are
'     RUNTIME failures (both already seen and safely caught: E_INVALIDARG
'     on AddTitleBlock's value, "member not found" on Sheet.BendTables).
'   * The error message itself gave the real signature verbatim — as good
'     as an IntelliSense tooltip, since it's the compiler reporting what
'     it actually resolved: AddTitleBlock(TitleBlockDefinition As Object,
'     [TitleBlockLocation As Object], [PromptStrings As Object]). First
'     parameter required, hence the crash.
'   * ApplySheetFormat: removed the bare AddTitleBlock() attempt entirely.
'     Down to one mechanism now — a TitleBlockDefinition freshly looked up
'     from the document's own TitleBlockDefinitions collection by name —
'     which was never actually exercised before, since the compile error
'     always aborted the rule before reaching it.
'   * Every other call in the file was re-audited specifically against
'     this risk (right method, wrong argument count) — this was the only
'     offender; everything else has either run cleanly across multiple
'     real executions already or mirrors a call shape that has.
'
'  v7 — title block has now failed FIVE distinct ways, all with the exact
'  same E_INVALIDARG (captured-instance object, captured-instance name
'  string x2, ThisDrawing wrapper, freshly-looked-up-by-name object). A
'  real run confirmed the v6 fresh-lookup attempt reaches AddTitleBlock
'  with what looks like a valid TitleBlockDefinition (no separate lookup
'  error) and STILL gets rejected — so this isn't about finding the right
'  object, something else is wrong.
'   * Split the lookup and the AddTitleBlock call into separate Try blocks
'     so the next run's log says definitively which one is throwing,
'     rather than one shared message covering both.
'   * One more hypothesis, grounded in real reference code rather than
'     imagination: createSheets' only confirmed-working AddTitleBlock call
'     always supplies the 3rd PromptStrings argument (even just empty
'     strings) — every attempt in this file so far has omitted it entirely.
'     Trying a 2-empty-string array now, matching that reference's shape
'     (its exact required length for THIS title block is unknown).
'   * If this ALSO fails identically: treat that as the signal to stop
'     guessing entirely and get a screenshot of what IntelliSense shows
'     immediately after typing "oSheet.AddTitleBlock(" in the iLogic editor
'     — the compiler error already gave the signature, but every parameter
'     is typed Object, so the signature alone can't reveal what values are
'     actually valid. This is the same technique (screenshot of the
'     Inventor UI) that already unblocked the balloon/border/title-block
'     wrapper calls earlier in this project — worth reaching for now rather
'     than a 7th blind code guess.
' =====================================================================

Imports System.Collections.Generic

Sub Main()

    ' ---------------- CONSTANTS — EDIT THESE ----------------
    Dim TemplatePath As String = "C:\VAULTWorkingFolder\Engineering\CAD Settings\TemplatesINV2024\acadglatt07.dwg"
    Dim OutputExt    As String = System.IO.Path.GetExtension(TemplatePath)   ' output format follows template (.dwg)
    Dim OutputPath   As String = ThisDoc.Path & "\" & ThisDoc.FileName(False) & "_DRAWINGS" & OutputExt

    ' View styles. kHiddenLineDrawingViewStyle / kHiddenLineRemovedDrawingViewStyle /
    ' kShadedDrawingViewStyle are all confirmed-in-the-wild members.
    Dim OrthoStyle As DrawingViewStyleEnum = kHiddenLineDrawingViewStyle       ' ortho views show hidden lines (drafting convention)
    Dim IsoStyle   As DrawingViewStyleEnum = kShadedDrawingViewStyle           ' confirmed working in baseline run
    Dim MainStyle  As DrawingViewStyleEnum = kShadedDrawingViewStyle           ' sheet-1 assembly view

    ' Sheet layout (cm, origin bottom-left). MarginBottom is large on purpose:
    ' it keeps views clear of a DIN-style title block strip along the bottom.
    ' Shrink it if your title block is smaller / positioned differently.
    Dim MarginL As Double = 1.5
    Dim MarginR As Double = 1.5
    Dim MarginT As Double = 1.5
    Dim MarginB As Double = 6.5
    Dim ViewGap As Double = 1.5
    Dim PartsListWidth As Double = 20.0    ' strip reserved on the right of sheet 1 for the parts list

    ' ---------------- VALIDATE ACTIVE DOC ----------------
    If ThisDoc.Document.DocumentType <> kAssemblyDocumentObject Then
        MessageBox.Show("Open the main assembly (.iam) and re-run.", "Wrong document type")
        Exit Sub
    End If

    Dim oAsmDoc As AssemblyDocument = ThisDoc.Document
    Dim oCompDef As AssemblyComponentDefinition = oAsmDoc.ComponentDefinition

    Try
        If TypeOf oCompDef Is WeldmentComponentDefinition Then
            Logger.Info("Assembly is a Weldment — Parts-Only BOM used below. " & _
                "Switch to Cut-List BOM manually if you want stock-length callouts instead.")
        End If
    Catch
        ' Advisory only — skip if this check is unavailable on this API surface
    End Try

    ' ---------------- BUILD UNIQUE PART LIST FROM BOM ----------------
    Dim oBOM As BOM = oCompDef.BOM
    oBOM.StructuredViewEnabled = True
    oBOM.StructuredViewFirstLevelOnly = False
    Try
        oBOM.PartsOnlyViewEnabled = True   ' needed so the kPartsOnly parts list has a view to bind to
    Catch ex As Exception
        Logger.Warn("Could not enable Parts Only BOM view: " & ex.Message)
    End Try
    Dim oBOMView As BOMView = oBOM.BOMViews.Item("Structured")

    Dim uniqueParts As New Dictionary(Of String, Document)
    CollectLeafParts(oBOMView.BOMRows, uniqueParts)
    Logger.Info(uniqueParts.Count & " unique part(s) found in BOM.")

    ' ---------------- CREATE DRAWING DOC ----------------
    Dim sTemplate As String = TemplatePath
    If String.IsNullOrEmpty(sTemplate) Then
        Try
            sTemplate = ThisApplication.FileManager.GetTemplateFile(kDrawingDocumentObject)
        Catch ex As Exception
            MessageBox.Show("Could not auto-resolve a default drawing template. " & _
                "Set TemplatePath at the top of the rule and re-run.", "Template not found")
            Exit Sub
        End Try
    End If

    If Not System.IO.File.Exists(sTemplate) Then
        MessageBox.Show("Template file does not exist:" & vbCrLf & sTemplate, "Bad template path")
        Exit Sub
    End If

    Logger.Info("Resolved template: " & sTemplate)

    Dim oDrawDoc As DrawingDocument
    Try
        oDrawDoc = ThisApplication.Documents.Add(kDrawingDocumentObject, sTemplate, True)
    Catch ex As Exception
        MessageBox.Show("Documents.Add rejected this template file:" & vbCrLf & sTemplate & vbCrLf & _
            ex.Message, "Documents.Add failed")
        Exit Sub
    End Try
    Dim oTG As TransientGeometry = ThisApplication.TransientGeometry

    ' ---------------- SHEET 1 : MAIN ASSEMBLY ----------------
    Dim oMainSheet As Sheet = oDrawDoc.ActiveSheet
    oMainSheet.Name = "MAIN ASSEMBLY"

    ' Remember sheet 1's title block name + paper size ("Glatt_Norm_eng") so
    ' sheets 2..N can reuse them — baseline run left new sheets bare. Border
    ' needs no name: AddDefaultBorder() in ApplySheetFormat has worked cleanly
    ' on every run so far, no lookup required.
    Dim sTBName As String = ""
    Dim eMainSize As PaperSizeEnum = kA3PaperSize
    Try
        If Not (oMainSheet.TitleBlock Is Nothing) Then sTBName = oMainSheet.TitleBlock.Name
        eMainSize = oMainSheet.Size
    Catch ex As Exception
        Logger.Warn("Could not read title block/size from sheet 1: " & ex.Message)
    End Try

    ' Main view: create 1:1, measure, then fit into the area left of the parts list strip
    Dim oMainView As DrawingView = AddViewSafe(oMainSheet, oAsmDoc, _
        oTG.CreatePoint2d(oMainSheet.Width * 0.4, oMainSheet.Height * 0.55), 1.0, _
        kIsoTopRightViewOrientation, MainStyle, "MAIN ASSEMBLY")

    Dim oPartsList As PartsList = Nothing
    If Not (oMainView Is Nothing) Then
        Dim regionW As Double = oMainSheet.Width - MarginL - MarginR - PartsListWidth
        Dim regionH As Double = oMainSheet.Height - MarginB - MarginT
        Dim sFit As Double = Math.Min(regionW / Math.Max(oMainView.Width, 0.001), _
                                      regionH / Math.Max(oMainView.Height, 0.001))
        If sFit > 0 Then
            Dim s As Double = SnapScale(sFit)
            SetScaleSafe(oMainView, s, "MAIN ASSEMBLY")
            SetPosSafe(oMainView, MarginL + regionW / 2, MarginB + regionH / 2)
            Logger.Info("Main assembly view scale set to " & s)
        End If

        ' Parts list. Third arg is PartsListLevelEnum as a raw value:
        '   46594 = kPartsOnly (all leaf parts, flattened — what we want here)
        '   46593 = kStructured (first-level items)
        ' Numeric-value pattern confirmed in working code (JRForman/createSheets).
        ' Placement point = TOP-LEFT corner of the table; it grows downward.
        Dim oPLPos As Point2d = oTG.CreatePoint2d(oMainSheet.Width - MarginR - PartsListWidth, _
                                                  oMainSheet.Height - 1.2)
        Try
            oPartsList = oMainSheet.PartsLists.Add(oMainView, oPLPos, 46594)
        Catch ex As Exception
            Logger.Warn("PartsLists.Add(kPartsOnly=46594) failed: " & ex.Message & _
                " — retrying with the default level.")
            Try
                oPartsList = oMainSheet.PartsLists.Add(oMainView, oPLPos)
            Catch ex2 As Exception
                Logger.Warn("PartsLists.Add failed entirely: " & ex2.Message & _
                    ". Continuing without parts list / balloons.")
            End Try
        End Try

        If Not (oPartsList Is Nothing) Then
            AutoBalloonView(oMainSheet, oMainView, oAsmDoc)
        End If
    End If

    ' ---------------- ONE SHEET PER UNIQUE PART ----------------
    Dim failCount As Integer = 0
    For Each oDoc As Document In uniqueParts.Values
        Try
            BuildPartSheet(oDrawDoc, oDoc, sTBName, eMainSize, OrthoStyle, IsoStyle, _
                MarginL, MarginR, MarginT, MarginB, ViewGap)
        Catch ex As Exception
            failCount = failCount + 1
            Logger.Warn("Sheet failed for part '" & oDoc.DisplayName & "': " & ex.Message)
        End Try
    Next
    If failCount > 0 Then
        Logger.Warn(failCount & " part sheet(s) failed — see warnings above. Drawing still saved with the rest.")
    End If

    ' ---------------- SAVE ----------------
    oDrawDoc.SaveAs(OutputPath, False)   ' confirmed working with DWG-native doc in baseline run
    Logger.Info("Saved: " & OutputPath)

End Sub


' =====================================================================
Sub BuildPartSheet(oDrawDoc As DrawingDocument, oPartDoc As Document, _
        sTBName As String, eSize As PaperSizeEnum, _
        OrthoStyle As DrawingViewStyleEnum, IsoStyle As DrawingViewStyleEnum, _
        MarginL As Double, MarginR As Double, MarginT As Double, MarginB As Double, _
        ViewGap As Double)
' One sheet per part: FRONT / TOP / RIGHT third-angle arrangement + ISO, at a
' common standard scale that fits the sheet.
'
' Third angle is enforced by PLACEMENT of independent base views (TOP directly
' ABOVE the front view, RIGHT view to the RIGHT of it) with explicit
' orientations — deliberately not AddProjectedView, whose direction convention
' would follow the template's (likely first-angle DIN) drafting standard.
'
' NOTE: kFrontViewOrientation follows how each part was modeled in its own
' coordinate system — "front" is the part's XY-plane-facing view, which may not
' be the face a drafter would pick. Consistent, but review on first run.

    Dim oTG As TransientGeometry = ThisApplication.TransientGeometry
    Dim oSheet As Sheet = oDrawDoc.Sheets.Add()   ' bare Add() confirmed working in baseline run

    Try
        oSheet.Name = Left(System.IO.Path.GetFileNameWithoutExtension(oPartDoc.FullFileName), 30)
    Catch ex As Exception
        Logger.Warn("Could not rename sheet for '" & oPartDoc.DisplayName & "': " & ex.Message)
    End Try

    Try
        oSheet.Size = eSize   ' Sheets.Add() does not reliably inherit sheet 1's paper size
    Catch ex As Exception
        Logger.Warn("Could not set paper size on sheet '" & oSheet.Name & "': " & ex.Message)
    End Try

    ApplySheetFormat(oDrawDoc, oSheet, sTBName)

    If IsSheetMetal(oPartDoc) Then
        BuildSheetMetalViews(oSheet, oPartDoc, OrthoStyle, IsoStyle, MarginL, MarginR, MarginT, MarginB)
        Exit Sub
    End If

    ' ---------------- non-sheet-metal: FRONT/TOP/RIGHT + ISO ----------------
    ' Create all four views 1:1 mid-sheet (they will overflow the sheet edges —
    ' harmless and transient), measure, then rescale + position.
    Dim oC As Point2d = oTG.CreatePoint2d(oSheet.Width / 2, oSheet.Height / 2)
    Dim vFront As DrawingView = AddViewSafe(oSheet, oPartDoc, oC, 1.0, kFrontViewOrientation, OrthoStyle, "FRONT")
    Dim vTop   As DrawingView = AddViewSafe(oSheet, oPartDoc, oC, 1.0, kTopViewOrientation, OrthoStyle, "TOP")
    Dim vRight As DrawingView = AddViewSafe(oSheet, oPartDoc, oC, 1.0, kRightViewOrientation, OrthoStyle, "RIGHT")
    Dim vIso   As DrawingView = AddViewSafe(oSheet, oPartDoc, oC, 1.0, kIsoTopRightViewOrientation, IsoStyle, "ISO")

    If vFront Is Nothing And vTop Is Nothing And vRight Is Nothing And vIso Is Nothing Then
        Logger.Warn("No views could be created for '" & oPartDoc.DisplayName & "' — sheet left empty.")
        Exit Sub
    End If

    ' At scale 1:1, view Width/Height (cm on paper) == model extents (cm).
    ' Grid: left column = front with top stacked above; right column = right with iso above.
    Dim colL As Double = Math.Max(ViewW(vFront), ViewW(vTop))
    Dim colR As Double = Math.Max(ViewW(vRight), ViewW(vIso))
    Dim rowB As Double = Math.Max(ViewH(vFront), ViewH(vRight))
    Dim rowT As Double = Math.Max(ViewH(vTop), ViewH(vIso))
    If (colL + colR) <= 0 Or (rowB + rowT) <= 0 Then Exit Sub

    Dim usableW As Double = oSheet.Width - MarginL - MarginR
    Dim usableH As Double = oSheet.Height - MarginB - MarginT
    Dim sFit As Double = Math.Min((usableW - ViewGap) / (colL + colR), _
                                  (usableH - ViewGap) / (rowB + rowT))
    If sFit <= 0 Then Exit Sub
    Dim s As Double = SnapScale(sFit)

    SetScaleSafe(vFront, s, "FRONT")
    SetScaleSafe(vTop, s, "TOP")
    SetScaleSafe(vRight, s, "RIGHT")
    SetScaleSafe(vIso, s, "ISO")

    ' Re-measure at final scale, then place the third-angle grid:
    '   TOP shares the front view's vertical centerline (directly above it),
    '   RIGHT shares the front view's horizontal centerline (directly right of it).
    colL = Math.Max(ViewW(vFront), ViewW(vTop))
    colR = Math.Max(ViewW(vRight), ViewW(vIso))
    rowB = Math.Max(ViewH(vFront), ViewH(vRight))
    rowT = Math.Max(ViewH(vTop), ViewH(vIso))

    Dim xL As Double = MarginL + colL / 2
    Dim xR As Double = MarginL + colL + ViewGap + colR / 2
    Dim yB As Double = MarginB + rowB / 2
    Dim yT As Double = MarginB + rowB + ViewGap + rowT / 2

    SetPosSafe(vFront, xL, yB)
    SetPosSafe(vTop, xL, yT)
    SetPosSafe(vRight, xR, yB)
    SetPosSafe(vIso, xR, yT)

    Logger.Info("Sheet '" & oSheet.Name & "': scale " & s)

End Sub


' =====================================================================
Sub BuildSheetMetalViews(oSheet As Sheet, oPartDoc As Document, _
        OrthoStyle As DrawingViewStyleEnum, IsoStyle As DrawingViewStyleEnum, _
        MarginL As Double, MarginR As Double, MarginT As Double, MarginB As Double)
' Sheet metal parts get FLAT PATTERN + BEND TABLE (for the brake operator)
' plus a folded ISO view for reference, matching the company's existing
' sheet metal drawing format — instead of FRONT/TOP/RIGHT orthographic views,
' which are less useful once a part is just a bent flat blank.
'
' <-- UNVERIFIED: Sheet.BendTables.Add(view, point) signature is from API
'     memory, not confirmed against this Inventor build (it is not in the
'     snippet browser dump or either linked repo). If it throws, type
'     "oSheet.BendTables.Add(" in the iLogic editor and read the IntelliSense
'     tooltip for the real parameter list — the same approach that fixed
'     PartsLists.Add earlier — then update the line below.

    Dim oTG As TransientGeometry = ThisApplication.TransientGeometry
    Dim oSMDef As SheetMetalComponentDefinition = TryCast(oPartDoc.ComponentDefinition, SheetMetalComponentDefinition)
    If oSMDef Is Nothing Then
        Logger.Warn("'" & oPartDoc.DisplayName & "' did not cast to SheetMetalComponentDefinition — skipping flat pattern/bend table.")
        Exit Sub
    End If

    Try
        If Not oSMDef.HasFlatPattern Then oSMDef.Unfold()
    Catch ex As Exception
        Logger.Warn("Could not unfold '" & oPartDoc.DisplayName & "' for a flat pattern: " & ex.Message)
    End Try

    Dim usableW As Double = oSheet.Width - MarginL - MarginR
    Dim usableH As Double = oSheet.Height - MarginB - MarginT

    ' ---- Flat pattern: upper-left, wide strip (matches the reference sheet) ----
    Dim oFlatPos As Point2d = oTG.CreatePoint2d(MarginL + usableW * 0.32, MarginB + usableH * 0.72)
    Dim oFlatView As DrawingView = AddFlatPatternViewSafe(oSheet, oPartDoc, oFlatPos, 1.0, OrthoStyle, "FLAT PATTERN")

    If Not (oFlatView Is Nothing) Then
        Dim sFit As Double = Math.Min((usableW * 0.62) / Math.Max(oFlatView.Width, 0.001), _
                                      (usableH * 0.5) / Math.Max(oFlatView.Height, 0.001))
        If sFit > 0 Then SetScaleSafe(oFlatView, SnapScale(sFit), "FLAT PATTERN")
        SetPosSafe(oFlatView, MarginL + usableW * 0.32, MarginB + usableH * 0.72)

        ' ---- Bend table: below the flat view ----
        ' <-- CONFIRMED WRONG by a real run: "Public member 'BendTables' on type 'Sheet' not
        '     found" — a clean member-not-found, not a bad-argument error, so this isn't a case
        '     of tweaking the call further. Needs ground truth: type "oSheet." in the iLogic
        '     editor and scan IntelliSense autocomplete for anything containing "Bend" or
        '     "Table" (also try "oFlatView." in case it hangs off the view/model side instead
        '     of the sheet). Left in place, Try/Catch-wrapped, so it keeps degrading gracefully
        '     rather than blocking the flat pattern/ISO views, which already work.
        Try
            Dim oBTPos As Point2d = oTG.CreatePoint2d(MarginL, MarginB + usableH * 0.32)
            oSheet.BendTables.Add(oFlatView, oBTPos)
        Catch ex As Exception
            Logger.Warn("Bend table failed for '" & oPartDoc.DisplayName & "': " & ex.Message & _
                " — Sheet.BendTables does not exist on this build (confirmed 'member not found', " & _
                "not a parameter issue). Type ""oSheet."" in the iLogic editor and scan IntelliSense " & _
                "for the real name/location, then update BuildSheetMetalViews(). Continuing without " & _
                "a bend table; flat pattern/ISO views are unaffected.")
        End Try
    Else
        Logger.Warn("No flat pattern view for '" & oPartDoc.DisplayName & _
            "' — confirm it has sheet metal features and a valid flat pattern.")
    End If

    ' ---- Folded ISO view: right side, for reference. No SheetMetalFoldedModel
    ' option is passed here, so (per createSheets) this defaults to the FOLDED shape. ----
    Dim oIsoPos As Point2d = oTG.CreatePoint2d(MarginL + usableW * 0.78, MarginB + usableH * 0.5)
    Dim oIsoView As DrawingView = AddViewSafe(oSheet, oPartDoc, oIsoPos, 1.0, kIsoTopRightViewOrientation, IsoStyle, "ISO")
    If Not (oIsoView Is Nothing) Then
        Dim sFit2 As Double = Math.Min((usableW * 0.4) / Math.Max(oIsoView.Width, 0.001), _
                                       (usableH * 0.75) / Math.Max(oIsoView.Height, 0.001))
        If sFit2 > 0 Then SetScaleSafe(oIsoView, SnapScale(sFit2), "ISO")
        SetPosSafe(oIsoView, MarginL + usableW * 0.78, MarginB + usableH * 0.5)
    End If

    Logger.Info("Sheet metal layout built for '" & oPartDoc.DisplayName & "'.")

End Sub


' =====================================================================
Function AddFlatPatternViewSafe(oSheet As Sheet, oDoc As Document, oPos As Point2d, _
        dScale As Double, eStyle As DrawingViewStyleEnum, sTag As String) As DrawingView
' ViewInfo NameValueMap key "SheetMetalFoldedModel" = False is the confirmed-in-the-wild
' way to get a flat-pattern base view (from createSheets-style production code — same
' repo already mined for the PartsLists.Add enum values — not API memory).
' Combining it with an explicit view name (6th positional arg) in the SAME call is NOT
' itself confirmed — retries without a name, then renames the result, if the named form throws.

    Dim oOpts As NameValueMap = ThisApplication.TransientObjects.CreateNameValueMap
    Try
        oOpts.Add("SheetMetalFoldedModel", False)
        oOpts.Add("DisplayForeshortenedTangentEdges", True)
        oOpts.Add("RetrieveDimensions", True)   ' <-- fresh, unconfirmed guess — see v5 header note
    Catch ex As Exception
        Logger.Warn("Could not build flat pattern ViewInfo options: " & ex.Message)
    End Try

    Try
        Return oSheet.DrawingViews.AddBaseView(oDoc, oPos, dScale, kDefaultViewOrientation, eStyle, sTag, , oOpts)
    Catch ex As Exception
        Logger.Warn("Flat pattern view '" & sTag & "' (named form) failed: " & ex.Message & _
            " — retrying without an explicit name.")
        Try
            Dim oV As DrawingView = oSheet.DrawingViews.AddBaseView(oDoc, oPos, dScale, kDefaultViewOrientation, eStyle, , , oOpts)
            Try
                oV.Name = sTag
            Catch
                ' Cosmetic only — view is still usable under its default name
            End Try
            Return oV
        Catch ex2 As Exception
            Logger.Warn("Flat pattern view failed entirely on sheet '" & oSheet.Name & "': " & ex2.Message)
            Return Nothing
        End Try
    End Try

End Function


' =====================================================================
Function IsSheetMetal(oDoc As Document) As Boolean
' TypeOf-based check, matching the same pattern already used for the assembly-
' level Weldment check — safer than assuming an "IsSheetMetal" property exists,
' or comparing the "Document SubType Name" iProperty string, which is
' UI-language-dependent (this Inventor install appears to be German).
    Try
        Return TypeOf oDoc.ComponentDefinition Is SheetMetalComponentDefinition
    Catch
        Return False
    End Try
End Function


' =====================================================================
Sub ApplySheetFormat(oDrawDoc As DrawingDocument, oSheet As Sheet, sTBName As String)
' Puts sheet 1's border + title block on a freshly added (bare) sheet.
'
' CONFIRMED from real runs: AddDefaultBorder() succeeds every time — no
' changes needed there.
'
' AddTitleBlock's REAL signature, straight from an Inventor compiler error
' (as good as an IntelliSense tooltip — this is the actual method the
' compiler resolved, not a guess):
'   Public Function AddTitleBlock(TitleBlockDefinition As Object,
'       [TitleBlockLocation As Object], [PromptStrings As Object]) As Inventor.TitleBlock
' The first parameter is REQUIRED. Calling it with zero arguments was not
' just wrong, it was a COMPILE error ("Argument not specified for parameter
' 'TitleBlockDefinition'"), which blocks the ENTIRE rule from running at
' all — Try/Catch cannot protect against a compile failure, since the rule
' never starts executing (not even the BOM-count log line got printed).
' That's a materially worse failure mode than any runtime E_INVALIDARG or
' "member not found" seen elsewhere in this file, and it's now removed.
'
' v7 update: a real run showed "TitleBlockDefinitions.Item(sTBName)" +
' AddTitleBlock(oTBDef) STILL failing with the identical E_INVALIDARG —
' the 5th distinct attempt to fail exactly the same way (captured-instance
' object, captured-instance name string x2, ThisDrawing wrapper, freshly-
' looked-up object). That log line couldn't tell us WHICH of the two calls
' inside the Try actually threw, so this version splits them into separate
' Try blocks for a clean answer next run.
'
' Also trying the one thing every CONFIRMED-WORKING AddTitleBlock call seen
' so far (createSheets) does differently from every attempt in this file:
' it always supplies the 3rd PromptStrings argument, even just empty
' strings, rather than omitting it. Every attempt here so far has omitted
' it. Worth testing since it's grounded in the one piece of real working
' reference code for this exact method, not another blind guess.
' <-- If this ALSO fails identically: I'm out of well-motivated hypotheses.
'     The most useful next step is a screenshot of what IntelliSense shows
'     immediately after typing "oSheet.AddTitleBlock(" in the iLogic editor
'     (same technique that worked for the snippet browser earlier) — that
'     shows argument types live, which the compiler error didn't fully
'     resolve (Object-typed params don't reveal what's actually valid).

    Try
        oSheet.AddDefaultBorder()
    Catch ex As Exception
        Logger.Warn("No border could be added to sheet '" & oSheet.Name & "': " & ex.Message)
    End Try

    If Not String.IsNullOrEmpty(sTBName) Then
        Dim oTBDef As TitleBlockDefinition = Nothing
        Try
            oTBDef = oDrawDoc.TitleBlockDefinitions.Item(sTBName)
        Catch ex As Exception
            Logger.Warn("TitleBlockDefinitions.Item(""" & sTBName & """) lookup failed on '" & _
                oSheet.Name & "': " & ex.Message & " — the name captured from sheet 1 doesn't resolve " & _
                "in this document's own title block library.")
        End Try

        If Not (oTBDef Is Nothing) Then
            Try
                Dim sPrompts(1) As String
                sPrompts(0) = ""
                sPrompts(1) = ""
                oSheet.AddTitleBlock(oTBDef, , sPrompts)
            Catch ex As Exception
                Logger.Warn("AddTitleBlock(oTBDef, , emptyPrompts) failed on '" & oSheet.Name & _
                    "' even with a valid TitleBlockDefinition in hand (lookup by name succeeded): " & _
                    ex.Message & ". This is the 6th distinct attempt failing the same way — see the " & _
                    "v7 header note for the screenshot ask that should unblock this for good.")
            End Try
        End If
    End If

End Sub


' =====================================================================
Function AddViewSafe(oSheet As Sheet, oDoc As Document, oPos As Point2d, dScale As Double, _
        eOrient As ViewOrientationTypeEnum, eStyle As DrawingViewStyleEnum, sTag As String) As DrawingView
' Named on creation (6th arg) — confirmed working across every run so far (every FRONT/TOP/
' RIGHT/ISO/MAIN ASSEMBLY view kept its intended name with zero warnings).
'
' "RetrieveDimensions" = True on the ViewInfo NameValueMap is a NEW, UNCONFIRMED attempt at
' pulling model dimensions onto every view — mirrors the Base View dialog's "Retrieve
' Dimensions" checkbox, same key/value pattern as the already-confirmed "SheetMetalFoldedModel"
' (see v5 header note). Unlike a wrong enum or member name, an unrecognized NameValueMap key
' is typically ignored rather than erroring, so this is lower-risk than most guesses here —
' but it still falls back to the confirmed-working plain call if the 8-arg form throws at all,
' rather than risk regressing something that already works.

    Dim oOpts As NameValueMap = ThisApplication.TransientObjects.CreateNameValueMap
    Try
        oOpts.Add("RetrieveDimensions", True)
    Catch
    End Try

    Try
        Return oSheet.DrawingViews.AddBaseView(oDoc, oPos, dScale, eOrient, eStyle, sTag, , oOpts)
    Catch ex As Exception
        Logger.Warn("View '" & sTag & "' with RetrieveDimensions failed: " & ex.Message & _
            " — retrying with the confirmed-working plain form (no dimension retrieval).")
        Try
            Return oSheet.DrawingViews.AddBaseView(oDoc, oPos, dScale, eOrient, eStyle, sTag)
        Catch ex2 As Exception
            Logger.Warn("View '" & sTag & "' failed entirely on sheet '" & oSheet.Name & "': " & ex2.Message)
            Return Nothing
        End Try
    End Try
End Function


Sub SetScaleSafe(oV As DrawingView, s As Double, sTag As String)
    If oV Is Nothing Then Exit Sub
    Try
        oV.Scale = s
    Catch ex As Exception
        Logger.Warn("Could not set scale on view '" & sTag & "': " & ex.Message)
    End Try
End Sub


Sub SetPosSafe(oV As DrawingView, x As Double, y As Double)
    If oV Is Nothing Then Exit Sub
    Try
        oV.Position = ThisApplication.TransientGeometry.CreatePoint2d(x, y)
    Catch ex As Exception
        Logger.Warn("Could not position a view: " & ex.Message)
    End Try
End Sub


Function ViewW(oV As DrawingView) As Double
    If oV Is Nothing Then Return 0
    Return oV.Width
End Function


Function ViewH(oV As DrawingView) As Double
    If oV Is Nothing Then Return 0
    Return oV.Height
End Function


Function SnapScale(sRaw As Double) As Double
' Largest standard (DIN ISO 5455-ish) scale that still fits.
    Dim stdScales() As Double = {10, 5, 2, 1, 1 / 2, 1 / 2.5, 1 / 5, 1 / 10, 1 / 20, 1 / 50, 1 / 100, 1 / 200}
    For Each s As Double In stdScales
        If s <= sRaw Then Return s
    Next
    Return sRaw   ' smaller than 1:200 — use the raw fit scale
End Function


' =====================================================================
Sub CollectLeafParts(oRows As BOMRowsEnumerator, ByRef dict As Dictionary(Of String, Document))
' Recurses structured BOM rows, keeps one Document per unique LEAF part
' (skips subassembly container rows, recurses into their ChildRows).
' Confirmed working in baseline run — part count matched the model.

    Dim oRow As BOMRow
    For Each oRow In oRows
        Dim oDef As ComponentDefinition = oRow.ComponentDefinitions.Item(1)
        Dim oPartDoc As Document = oDef.Document

        If oPartDoc.DocumentType = kPartDocumentObject Then
            Dim key As String = oPartDoc.FullFileName
            If Not dict.ContainsKey(key) Then dict.Add(key, oPartDoc)
        ElseIf Not (oRow.ChildRows Is Nothing) AndAlso oRow.ChildRows.Count > 0 Then
            CollectLeafParts(oRow.ChildRows, dict)
        End If
    Next

End Sub


' =====================================================================
Sub AutoBalloonView(oSheet As Sheet, oView As DrawingView, oAsmDoc As AssemblyDocument)
' CONFIRMED WORKING by a real run (Logger showed "5 balloon(s) placed on sheet
' 'MAIN ASSEMBLY:1'." with zero warnings). The View.Balloons.AttachToComponent(name)
' route tried afterward turned out to be unusable here: ThisDrawing can only ever
' refer to the document that HOSTS this rule (the assembly), never to a drawing
' document created programmatically mid-run — confirmed by the literal runtime
' error 'ThisDrawing: This document "MASTER FILE v1.iam" is not a drawing.' every
' time. Reverted to this classic-COM approach: one balloon per unique leaf part,
' leader attached to a real model edge via CreateGeometryIntent, placed on a ring
' just outside the view boundary.

    Dim oTG As TransientGeometry = ThisApplication.TransientGeometry
    Dim done As New HashSet(Of String)
    Dim ballooned As Integer = 0

    ' Leaf occurrences = actual parts, matching the Parts-Only list.
    ' Falls back to first-level occurrences if AllLeafOccurrences is unavailable.
    Dim oOccs As Object
    Try
        oOccs = oAsmDoc.ComponentDefinition.Occurrences.AllLeafOccurrences
    Catch
        oOccs = oAsmDoc.ComponentDefinition.Occurrences
        Logger.Warn("AllLeafOccurrences unavailable — ballooning first-level occurrences only.")
    End Try

    Dim vc As Point2d = oView.Position
    Dim ringR As Double = Math.Max(oView.Width, oView.Height) / 2 + 2.0

    For Each oOcc As ComponentOccurrence In oOccs
        Try
            If oOcc.Suppressed Then Continue For
            Dim key As String = oOcc.ReferencedDocumentDescriptor.FullDocumentName
            If done.Contains(key) Then Continue For

            Dim oCurves As DrawingCurvesEnumerator = oView.DrawingCurves(oOcc)
            If oCurves.Count = 0 Then Continue For   ' part not visible in this view

            ' First curve that yields a usable attach point (closed curves like
            ' circles have no Mid/StartPoint — fall back to CenterPoint).
            Dim oCurve As DrawingCurve = Nothing
            Dim oAttach As Point2d = Nothing
            For Each c As DrawingCurve In oCurves
                Dim p As Point2d = c.MidPoint
                If p Is Nothing Then p = c.StartPoint
                If p Is Nothing Then p = c.CenterPoint
                If Not (p Is Nothing) Then
                    oCurve = c
                    oAttach = p
                    Exit For
                End If
            Next
            If oAttach Is Nothing Then Continue For

            ' Balloon sits on a ring outside the view, radially out from the
            ' view centre through the attach point, clamped onto the sheet.
            Dim dx As Double = oAttach.X - vc.X
            Dim dy As Double = oAttach.Y - vc.Y
            Dim mag As Double = Math.Sqrt(dx * dx + dy * dy)
            If mag < 0.001 Then
                dx = 0 : dy = 1 : mag = 1
            End If
            Dim bx As Double = Math.Min(Math.Max(vc.X + dx / mag * ringR, 1), oSheet.Width - 1)
            Dim by As Double = Math.Min(Math.Max(vc.Y + dy / mag * ringR, 1), oSheet.Height - 1)

            Dim oIntent As GeometryIntent = oSheet.CreateGeometryIntent(oCurve, oAttach)
            Dim oLeader As ObjectCollection = ThisApplication.TransientObjects.CreateObjectCollection
            oLeader.Add(oTG.CreatePoint2d(bx, by))
            oLeader.Add(oIntent)
            oSheet.Balloons.Add(oLeader)

            done.Add(key)
            ballooned = ballooned + 1
        Catch ex As Exception
            Logger.Warn("Balloon failed for occurrence '" & oOcc.Name & "': " & ex.Message)
        End Try
    Next

    Logger.Info(ballooned & " balloon(s) placed on sheet '" & oSheet.Name & "'.")

End Sub
